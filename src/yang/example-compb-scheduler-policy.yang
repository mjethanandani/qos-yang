module example-compb-scheduler-policy {
  yang-version 1.1;
  namespace "urn:ietf:params:xml:ns:yang:" +
            "example-compb-scheduler-policy";
  prefix scheduler-plcy;

  import ietf-qos-action {
    prefix qos-action;
    reference
      "RFC XXXX: A YANG Data Model for Quality of Service (QoS).";
  }
  import ietf-traffic-policy {
    prefix traffic-policy;
    reference
      "RFC XXXX: A YANG Data Model for Quality of Service (QoS).";
  }

  organization
    "Company B";

  contact
    "Editor:   XYZ
               <mailto:xyz@compb.com>";

  description
    "This module defines a scheduler policy. The classification
     is based on classifier-any, and the action is a scheduler.";

  revision YYYY-MM-DD {
    description
      "Initial revision of diffserv policy";
    reference
      "RFC XXXX: A YANG Data Model for Quality of Service (QoS).";
  }

  grouping queue-policy-name {
    container compb-queue-policy-name {
      leaf name {
        type string;
        description
          "Queue policy name";
      }
      description
        "compb-queue-policy container";
    }
    description
      "compb-queue policy grouping";
  }

  augment "/traffic-policy:policies" +
    "/traffic-policy:policy" +
    "/traffic-policy:classifier" +
    "/traffic-policy:action" {
    choice action-params {
      case scheduler {
        uses qos-action:scheduler;
      }
      case queue-policy {
        uses queue-policy-name;
      }
      description
        "Augment the scheduler policy with a queue policy";
    }
    description
      "Augmentation of the scheduler policy with a queue policy";
  }
}
