module example-compa-diffserv {
  yang-version 1.1;
  namespace "urn:ietf:params:xml:ns:yang:example-compa-diffserv";
  prefix example;

  import ietf-qos-types {
    prefix qos-types;
    reference
      "RFC XXXX: YANG Models for Quality of Service (QoS).";
  }
  import ietf-traffic-policy {
    prefix traffic-policy;
    reference
      "RFC XXXX: YANG Models for Quality of Service (QoS).";
  }
  import ietf-qos-action {
    prefix qos-action;
    reference
      "RFC XXXX: YANG Models for Quality of Service (QoS).";
  }
  import ietf-diffserv {
    prefix diffserv;
    reference
      "RFC XXXX: YANG Models for Quality of Service (QoS).";
  }
  organization "Company A";
  contact
    "Editor:   XYZ
              <mailto:xyz@compa.com>";
  description
    "This module contains a collection of YANG definitions of
     companyA diffserv specification extension.";
  revision YYYY-MM-DD {
    description
      "Initial revision for diffserv actions on network packets.";
    reference
      "RFC XXXX: A YANG Data Model for Quality of Service (QoS).";
  }

  identity default-policy-type {
    base qos-types:policy-type;
    description
      "This defines default policy-type.";
  }

  identity qos-group {
    base qos-types:filter-type;
    description
      "Filter-type to match on  packet metadata. This metadata
       can be used for packet marking, queuing for traffic in
       egress direction.";
  }

  grouping qos-group {
    list qos-group {
      key "min max";
      description
        "List of qos-groups to match on. A QoS group is a set of
         packets tagged as group.";
      leaf min {
        type uint8;
        description
          "Minimum value of qos-group range.";
      }
      leaf max {
        type uint8;
        must ". >= ../min" {
          error-message
          "The qos-group max must be 
           greater than or equal to qos-group min.";
        }
        description
          "Maximum value of qos-group range.";
      }
    }
    description
      "Filter containing list of qos-group ranges.";
  }
  grouping bw-remaining-percent {
    container bw-remaining-percent {
      leaf value {
        type uint8;
        units "percentage";
        description
          "Percentage of the remaining bandwidth present.";
      }
      description
        "Remaining bandwidth of the link in percent.";
    }
    description
      "Grouping for bandwidth remaining after
      reserved and priority bandwidth.";
  }
  grouping qos-group-marking {
    container qos-group {
      leaf qos-group {
        type uint8;
        description
          "Mark metadata information in the network packet";
      }
      description
        "Container for QoS-Group marking.";
    }
    description
      "Grouping for QoS-Group marking.";
  }

  augment "/traffic-policy:classifiers/" +
    "traffic-policy:classifier/" +
    "traffic-policy:filter/diffserv:filter-param" {
    case qos-group {
      uses qos-group;
      description
        "Filter containing list of qos-group ranges.
        QoS-group represent packet metadata information
        in a network packet.";
    }
    description
      "Augmentation of classifier filters.";
  }

  augment "/traffic-policy:policies/traffic-policy:policy/" +
    "traffic-policy:classifier/" +
    "traffic-policy:action" {
    choice action-params {
      case priority {
	uses qos-action:priority;
      }
      case min-rate {
	uses qos-action:min-rate;
      }
      case max-rate {
	uses qos-action:max-rate;
      }
      case bw-remaining {
	uses bw-remaining-percent;
      }
      case mark-qos-group {
	uses qos-group-marking;
      }
      description
	"Choice of action parameters.";
    }
    description
      "Augments policy entry to add action parameters.";
  }

  augment "/traffic-policy:policies" +
    "/traffic-policy:policy" +
    "/traffic-policy:classifier" +
    "/traffic-policy:action" +
    "/diffserv:action-params" +
    "/diffserv:meter-inline" +
    "/diffserv:meter-types" +
    "/diffserv:single-rate-two-color-meter-type" +
    "/diffserv:single-rate-two-color-meter" {
    description
      "Augment the single-rate-two-color meter to add" +
      "color classifiers.";
    container conform-color {
      uses traffic-policy:generic-classifier-attr;
      description
        "Conform color classifier container.";
    }
    container exceed-color {
      uses traffic-policy:generic-classifier-attr;
      description
        "Exceed color classifier container.";
    }
  }

  augment "/traffic-policy:policies" +
    "/traffic-policy:policy" +
    "/traffic-policy:classifier" +
    "/traffic-policy:action" +
    "/diffserv:action-params" +
    "/diffserv:meter-inline" +
    "/diffserv:meter-types" +
    "/diffserv:single-rate-three-color-meter-type" +
    "/diffserv:single-rate-three-color-meter" {
    description
      "Augment the one-rate-tri-color meter to add" +
      "color classifiers.";
    container conform-color {
      uses traffic-policy:generic-classifier-attr;
      description
        "Conform color classifier container.";
    }
    container exceed-color {
      uses traffic-policy:generic-classifier-attr;
      description
        "Exceed color classifier container.";
    }
    container violate-color {
      uses traffic-policy:generic-classifier-attr;
      description
        "Violate color classifier container.";
    }
  }

  augment "/traffic-policy:policies" +
    "/traffic-policy:policy" +
    "/traffic-policy:classifier" +
    "/traffic-policy:action" +
    "/diffserv:action-params" +
    "/diffserv:meter-inline" +
    "/diffserv:meter-types" +
    "/diffserv:two-rate-three-color-meter-type" +
    "/diffserv:two-rate-three-color-meter" {
    description
      "Augment the two-rate-tri-color meter to add" +
      "color classifiers.";
    container conform-color {
      uses traffic-policy:generic-classifier-attr;
      description
        "Conform color classifier container.";
    }
    container exceed-color {
      uses traffic-policy:generic-classifier-attr;
      description
        "Exceed color classifier container.";
    }
    container violate-color {
      uses traffic-policy:generic-classifier-attr;
      description
        "Violate color classifier container.";
    }
  }
}
