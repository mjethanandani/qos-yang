module ietf-scheduler-policy {
  yang-version 1.1;
  namespace "urn:ietf:params:xml:ns:yang:ietf-scheduler-policy";
  prefix scheduler-policy;

  import ietf-traffic-policy {
    prefix traffic-policy;
  }
  import ietf-qos-action {
    prefix qos-action;
  }
  import ietf-diffserv {
    prefix diffserv;
  }
  import ietf-qos-types {
    prefix qos-types;
    reference
      "RFC XXXX: YANG Models for Quality of Service (QoS).";
  }

  organization
    "IETF Routing Area Working Group.";

  contact
    "WG Web:   <https://datatracker.ietf.org/wg/rtgwg/>
     WG List:  <mailto:rtgwg@ietf.org>

     Editor:   Aseem Choudhary
               <mailto:asechoud@cisco.com>
     Editor:   Mahesh Jethanandani
               <mailto:mjethanandani@gmail.com>";

  description
    "This module contains a collection of YANG definitions for
     configuring QoS scheduler policies.

     Copyright (c) 2023 IETF Trust and the persons identified as
     authors of the code.  All rights reserved.

     Redistribution and use in source and binary forms, with or
     without modification, is permitted pursuant to, and subject
     to the license terms contained in, the Revised BSD License
     set forth in Section 4.c of the IETF Trust's Legal Provisions
     Relating to IETF Documents
     (http://trustee.ietf.org/license-info).

     This version of this YANG module is part of RFC XXXX; see
     the RFC itself for full legal notices.";

  revision YYYY-MM-DD {
    description
      "Initial version.";
    reference
      "RFC XXXX: YANG Models for Quality of Service (QoS).";
  }

  augment "/traffic-policy:policies/traffic-policy:policy" +
          "/traffic-policy:classifier/traffic-policy:inline" +
          "/traffic-policy:filter" {
    when "derived-from-or-self(../../../traffic-policy:type, " +
         "'qos-types:scheduler-policy-type')" {
      description
        "This filter can be used only when policy type is
         scheduler-policy.";
    }
    choice filter-params {
      description
        "Choice of filter parameters.";
      case filter-match-all {
        uses diffserv:filter-match-all;
        description
          "A filter that matches all packets.";
      }
    }
    description
      "Augments Queue Policy Classifier to add filter parameters.";
  }

  augment "/traffic-policy:policies/traffic-policy:policy/" +
          "traffic-policy:classifier/traffic-policy:action" {
    when "derived-from-or-self(../../traffic-policy:type, " +
         "'qos-types:scheduler-policy-type')" {
      description
        "These actions apply only when policy type is
         scheduler-policy.";
    }

    choice action-params {
      description
        "Choice of action parameters that can be taken.";

      case scheduler {
        uses qos-action:scheduler;
      }

      case queue-policy-name {
        container queue-policy-name {
          leaf queue-policy {
            type leafref  {
              path "/traffic-policy:policies/" +
                   "traffic-policy:policy/traffic-policy:name";
            }
            must "derived-from-or-self(/traffic-policy:policies" +
                 "/traffic-policy:policy/traffic-policy:type," +
                 "'qos-types:queue-policy-type')";
            mandatory true;
            description
              "This leafref refers to Queue Policy name.";
          }
          description
            "Container for Queue Policy name.";
        }
      }
    }
    description
      "Augments Queue Policy Classifier to add in Action parameters
       for Scheduler policy.";
  }
}
