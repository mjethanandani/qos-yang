module example-compb-queue-policy {
  yang-version 1.1;
  namespace "urn:ietf:params:xml:ns:yang:example-compb-queue-policy";
  prefix queue-plcy;

  import ietf-qos-types {
    prefix qos-types;
    reference
      "RFC XXXX: YANG Models for Quality of Service (QoS).";
  }
  import ietf-traffic-policy {
    prefix traffic-policy;
  }

  organization "Company B";
  contact
    "Editor:   XYZ
              <mailto:xyz@compb.com>";

  description
    "This module defines a queue policy. The classification
     is based on aforwarding class, and the actions are queues.

     Copyright (c) 2014 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX; see
     the RFC itself for full legal notices.";

  revision YYYY-MM-DD {
    description
      "Initial revision of diffserv policy";
    reference
      "RFC XXXX: A YANG Data Model for Quality of Service (QoS).";
  }

  identity compb-queue {
    base qos-types:action-type;
    description
      "compb-queue action type";
  }

  grouping compb-queue-name {
    container queue-name {
      leaf name {
        type string;
        description
          "Queue class name";
      }
      description
        "compb queue container";
    }
    description
      "compb-queue grouping";
  }
  
  augment "/traffic-policy:policies" +
          "/traffic-policy:policy" +
          "/traffic-policy:classifier" +
          "/traffic-policy:action" {
    choice action-params {
      description
        "Choice of action types";
      case compb-queue {
        uses compb-queue-name;
      }
    }
    description
      "Augment the queue actions to queue policy entry";
  }
}
