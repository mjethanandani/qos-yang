module example-compb-diffserv-filter-policy {
     yang-version 1;
     namespace "urn:ietf:params:xml:ns:yang:example-compb-diffserv-filter-policy";
     prefix compb-filter-policy;

///  import ietf-interfaces {
///    prefix if;
///  }
  import ietf-qos-classifier {
    prefix classifier;
  }
  import ietf-qos-policy {
    prefix policy;
  }
  import ietf-qos-action {
    prefix action;
  }
////  import ietf-diffserv-target {
////    prefix target;
////  }
  import ietf-diffserv {
    prefix diffserv;
  }

  organization "Company B";
  contact
    "Editor:   XYZ
              <mailto:xyz@compb.com>";

  description
    "This module contains a collection of YANG definitions for
     configuring diffserv specification implementations.

     Copyright (c) 2014 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX; see
     the RFC itself for full legal notices.";

  revision 2015-04-07 {
    description
      "Latest revision of diffserv policy";
    reference "RFC XXXX";
  }


  /* 
   * The policy must be of either type v4 or v6. Corresponding
   * address types must be used. Enforce with "must" statement?
   */ 
  identity v4-diffserv-policy-type {
    base policy:policy-type;
    description
      "This defines default policy-type";
  }

  identity v6-diffserv-policy-type {
    base policy:policy-type;
    description
      "This defines default policy-type";
  }

  /*************************************************
   * Classification types
   *************************************************/

  identity forwarding-class {
      base classifier:filter-type;
      description
        "Forwarding class filter type";
  }

  identity internal-loss-priority  {
     base classifier:filter-type;
     description
        "Internal loss priority filter type";
  }

  grouping forwarding-class-cfg {
    list forwarding-class-cfg {
      key "forwarding-class";
      description
        "list of forwarding-classes";
      leaf forwarding-class {
        type string;
        description
          "Forwarding class name";
      }
    }
    description
      "Filter containing list of forwarding classes";
  }

  grouping loss-priority-cfg {
    list loss-priority-cfg {
      key "loss-priority";
      description
        "list of loss-priorities";
      leaf loss-priority {
        type enumeration {
          enum high {
           description "High Loss Priority";
          }
          enum medium-high {
           description "Medium-high Loss Priority";
          }
          enum medium-low {
           description "Medium-low Loss Priority";
          }
          enum low {
           description "Low Loss Priority";
          }
        }
        description
          "Loss-priority";
      }
    }
    description
      "Filter containing list of loss priorities";
  }

  augment "/policy:policies" +
          "/policy:policy-entry" +
          "/policy:classifier-entry" +
          "/policy:filter-entry" +
          "/diffserv:filter-params" {
    case forwarding-class {
        uses forwarding-class-cfg;
      description
        "Filter Type Internal-loss-priority";
    }
    case internal-loss-priority {
        uses loss-priority-cfg;
      description
        "Filter Type Internal-loss-priority";
    }
    description 
      "Augments Diffserv Classifier with vendor" +
      " specific types";
  }

  /*************************************************
   * Actions 
   *************************************************/

  identity mark-fwd-class {
    base policy:action-type;
    description
      "mark forwarding class action type";
  }

  identity mark-loss-priority {
    base policy:action-type;
    description
      "mark loss-priority action type";
  }

  grouping mark-fwd-class {
    container mark-fwd-class-cfg {
      leaf forwarding-class {
        type string;
        description
          "Forwarding class name";
      }
      description
        "mark-fwd-class container";
    }
    description
      "mark-fwd-class grouping";
  }

  grouping mark-loss-priority {
    container mark-loss-priority-cfg {
      leaf loss-priority {
        type enumeration {
          enum high {
           description "High Loss Priority";
          }
          enum medium-high {
           description "Medium-high Loss Priority";
          }
          enum medium-low {
           description "Medium-low Loss Priority";
          }
          enum low {
           description "Low Loss Priority";
          }
        }
        description
          "Loss-priority";
      }
      description
        "mark-loss-priority container";
    }
    description
      "mark-loss-priority grouping";
  }

  augment "/policy:policies" +
          "/policy:policy-entry" +
          "/policy:classifier-entry" +
          "/policy:classifier-action-entry-cfg" +
          "/diffserv:action-cfg-params" {
    case mark-fwd-class {
      uses mark-fwd-class;
      description
        "Mark forwarding class in the packet";
    }
    case mark-loss-priority {
        uses mark-loss-priority;
      description
        "Mark loss priority in the packet";
    }
    case meter-reference {
        uses action:meter-reference;
      description
        "Assign a meter as an action";
    }
    case discard {
        uses action:discard;
      description
        "Discard action";
    }
    case count {
        uses action:count;
      description
        "Count action - explicit count configuration";
    }
    description 
      "Augments common diffserv policy actions";
  }
  
  augment "/action:meter-template" +
          "/action:meter-entry" +
          "/action:meter-type" +
          "/action:one-rate-tri-color-meter-type" +
          "/action:one-rate-tri-color-meter" {
     leaf one-rate-color-aware {
      type boolean;
      description
        "This defines if the meter is color-aware";
    }
  }
  augment "/action:meter-template" +
          "/action:meter-entry" +
          "/action:meter-type" +
          "/action:two-rate-tri-color-meter-type" +
          "/action:two-rate-tri-color-meter" {
     leaf two-rate-color-aware {
      type boolean;
      description
        "This defines if the meter is color-aware";
    }
  }
  
  /* example of augmenting a meter template with a
  /* vendor specific action */
  augment "/action:meter-template" +
          "/action:meter-entry" +
          "/action:meter-type" +
          "/action:two-parameter-token-bucket-meter-type" +
          "/action:two-parameter-token-bucket-meter" +
          "/action:exceed-action" +
          "/action:meter-action-params" +
          "/action:meter-action-val" {
    case meter-action-drop {
      description
          "meter drop";
           uses action:drop;
    }

    description
      "Augment the actions to basic meter";
  }
  
}
